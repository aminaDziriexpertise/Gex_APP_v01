(defun c:expa(/ js ok to1 to2)
 (setq ok T)
 (while (and (setq js (ssget "x" (list (cons 0 "insert")))) ok)
   (setq to1 (sslength js))
   (vla-sendcommand (vla-get-activedocument (vlax-get-acad-object)) "burst _all \n")
   (if (= to1 to2)
     (setq ok nil)
     (setq to2 to1)
   )
 )
)

(defun c:expl-p	()
 (vl-load-com)
 (vlax-for b (vla-get-Blocks
	(vla-get-ActiveDocument (vlax-get-acad-object))
      )
   (or	(wcmatch (vla-get-Name b) "`**_Space*")
(vla-put-explodable b :vlax-true)
   )
 )
 (princ)
) 

(defun c:CPL ( / ss)
  (if (setq ss (ssget '((0 . "LWPOLYLINE") (-4 . "<NOT") (-4 . "&") (70 . 1) (-4 . "NOT>"))))
    (command "_.PEDIT" "_M" ss "" "_Close" ""))
  (princ)
)
